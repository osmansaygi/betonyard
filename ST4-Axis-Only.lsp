;;; ============================================================
;;; ST4-Axis-Only.lsp - Sadece aks cizimi (egimli aks destekli)
;;;
;;; Axis data format:
;;;   1.kolon = tanjant (egim), 0 = duz aks
;;;   2.kolon = orijine uzaklik (m) - X veya Y koordinati
;;;   3,4,5.kolon = atanmamis
;;;
;;; 1. grup = Y akslari (yatay), 2. grup = X akslari (dikey) - orijinal mantik
;;; Tum akslar Z=0 duzleminde LINE olarak cizilir
;;; Komut: ST4AKS
;;; ============================================================

(defun C:ST4AKS ( / fn f line section lst
                   mesafeler egimler n i ybas x-koord y-koord x-egim y-egim
                   xmin xmax ymin ymax pt1 pt2
                   txt-ofs txt-h idx num yazi pos eg)
  (setq fn (getfiled "ST4 Dosyasi Secin" "" "st4" 0))
  (if (not fn)
    (princ "\nIptal.")
    (progn
      (setq f (open fn "r"))
      (if (not f)
        (princ "\nDosya acilamadi!")
        (progn
          (princ "\nAks verisi okunuyor...")
          (setq section nil mesafeler nil egimler nil)
          (while (setq line (read-line f))
            (cond
              ((wcmatch (strcase line) "*AXIS DATA*")
                (setq section "axis")
                (setq mesafeler nil egimler nil))
              ((wcmatch (strcase line) "*CIRCLE AXIS*")
                (setq section nil))
              ((and (= section "axis") (> (strlen line) 2))
                (if (and (not (wcmatch (strcase line) "/ *"))
                         (setq lst (ayir line))
                         (>= (length lst) 2))
                  (progn
                    (setq mesafeler (append mesafeler (list (atof (nth 1 lst)))))
                    (setq egimler (append egimler (list (atof (nth 0 lst))))))
                  )
              )
              (T nil)
            )
          )
          (close f)

          (if (not mesafeler)
            (princ "\nAks verisi bulunamadi.")
            (progn
              (setq n (length mesafeler))
              ;; Y baslangici: 2.kolon=0 ard arda iki satir; ikincisinin indeksi
              (setq ybas nil i 0)
              (while (and (< (1+ i) n) (not ybas))
                (if (and (> i 0)
                         (equal (nth i mesafeler) 0.0 1e-6)
                         (equal (nth (1+ i) mesafeler) 0.0 1e-6))
                  (setq ybas (1+ i))
                )
                (setq i (1+ i))
              )
              (if (not ybas)
                (setq ybas (fix (/ n 2)))
              )
              ;; 1. grup = Y konumlari (yatay), 2. grup = X konumlari (dikey)
              (setq y-koord '() y-egim '())
              (setq i 0)
              (while (< i ybas)
                (setq y-koord (append y-koord (list (nth i mesafeler))))
                (setq y-egim (append y-egim (list (if (< i (length egimler)) (nth i egimler) 0.0))))
                (setq i (1+ i))
              )
              (setq x-koord '() x-egim '())
              (while (< i n)
                (setq x-koord (append x-koord (list (nth i mesafeler))))
                (setq x-egim (append x-egim (list (if (< i (length egimler)) (nth i egimler) 0.0))))
                (setq i (1+ i))
              )
              ;; Cizim sinirlari (tum mesafelerden)
              (setq xmin (apply 'min (append x-koord (list 0))))
              (setq xmax (apply 'max (append x-koord (list 0))))
              (setq ymin (apply 'min (append y-koord (list 0))))
              (setq ymax (apply 'max (append y-koord (list 0))))
              (if (= xmin xmax) (setq xmin (- xmin 2) xmax (+ xmax 2)))
              (if (= ymin ymax) (setq ymin (- ymin 2) ymax (+ ymax 2)))

              (if (not (tblsearch "LAYER" "ST4-AKS"))
                (command "._LAYER" "_M" "ST4-AKS" "_C" "8" "" ""))
              (setq txt-ofs 0.5 txt-h 0.5)
              (setvar "CMDECHO" 0)
              ;; X akslari (dikey): egim=0 duz, egim!=0 egik cizgi (x = pos + egim*y)
              (setq idx 0)
              (while (< idx (length x-koord))
                (setq pos (nth idx x-koord)
                      eg (nth idx x-egim))
                (if (equal eg 0.0 1e-9)
                  (progn
                    (setq pt1 (list pos ymin 0.0))
                    (setq pt2 (list pos ymax 0.0))
                  )
                  (progn
                    (setq pt1 (list (+ pos (* eg ymin)) ymin 0.0))
                    (setq pt2 (list (+ pos (* eg ymax)) ymax 0.0))
                  )
                )
                (entmakex (list (cons 0 "LINE") (cons 8 "ST4-AKS")
                               (cons 10 pt1) (cons 11 pt2)))
                (setq pt1 (list (car pt2) (+ (cadr pt2) txt-ofs) 0.0))
                (entmakex (list (cons 0 "TEXT") (cons 8 "ST4-AKS")
                               (cons 10 pt1) (cons 40 txt-h) (cons 1 (itoa (1+ idx)))
                               (cons 50 0) (cons 72 1) (cons 73 2) (cons 11 pt1)))
                (setq idx (1+ idx))
              )
              ;; Y akslari (yatay): egim=0 duz, egim!=0 egik cizgi (y = pos + egim*x)
              (setq idx 0)
              (while (< idx (length y-koord))
                (setq pos (nth idx y-koord)
                      eg (nth idx y-egim))
                (if (equal eg 0.0 1e-9)
                  (progn
                    (setq pt1 (list xmin pos 0.0))
                    (setq pt2 (list xmax pos 0.0))
                  )
                  (progn
                    (setq pt1 (list xmin (+ pos (* eg xmin)) 0.0))
                    (setq pt2 (list xmax (+ pos (* eg xmax)) 0.0))
                  )
                )
                (entmakex (list (cons 0 "LINE") (cons 8 "ST4-AKS")
                               (cons 10 pt1) (cons 11 pt2)))
                (if (< idx 26)
                  (setq yazi (chr (+ 65 idx)))
                  (setq yazi (itoa (1+ idx)))
                )
                (setq pt1 (list (+ (car pt2) txt-ofs) (cadr pt2) 0.0))
                (entmakex (list (cons 0 "TEXT") (cons 8 "ST4-AKS")
                               (cons 10 pt1) (cons 40 txt-h) (cons 1 yazi)
                               (cons 50 0) (cons 72 0) (cons 73 2) (cons 11 pt1)))
                (setq idx (1+ idx))
              )
              (setvar "CMDECHO" 1)
              (command "._ZOOM" "_E")
              (princ (strcat "\n" (itoa (length x-koord)) " X aksi, " (itoa (length y-koord)) " Y aksi cizildi (Z=0). Katman: ST4-AKS"))
            )
          )
        )
      )
    )
  )
  (princ)
)

(defun list-head (lst k / r)
  (setq r '())
  (while (and lst (> k 0)) (setq r (append r (list (car lst))) lst (cdr lst) k (1- k)))
  r
)

(defun ayir (str / lst pos parca)
  (setq str (vl-string-trim " \t" str) lst '())
  (while (> (strlen str) 0)
    (if (setq pos (vl-string-search "," str))
      (setq parca (vl-string-trim " \t" (substr str 1 pos))
            str (vl-string-trim " \t" (substr str (+ pos 2))))
      (setq parca (vl-string-trim " \t" str) str ""))
    (setq lst (append lst (list parca)))
  )
  lst
)

(princ "\nST4 Aks yuklendi. Komut: ST4AKS")
(princ)
