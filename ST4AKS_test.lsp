;;; Test dosyasi - ST4AKS komutunun yuklenip yuklenmedigini kontrol eder
(defun C:ST4AKS ( / )
  (princ "\nST4AKS komutu calisti!")
  (princ)
)
(princ "\nST4AKS_test yuklendi. ST4AKS yazin.")
(princ)
